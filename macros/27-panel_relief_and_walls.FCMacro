# -*- coding: utf-8 -*-
"""
27-panel_relief_and_walls.FCMacro — MagicCardBox

Fixes the THIRD print's two mechanical complaints: the lid will not close, and the hinge
and magnets sit too close to the inside edge of the side walls.

WHY THE LID WOULD NOT CLOSE — it is not a tangency, it is a graze
-----------------------------------------------------------------
The lid's rear panel inner face and the box's rear face are BOTH flat planes at y = 36:

    panel inner face   y = 36.5  for z 0 .. 10.4      (PocketHingeWrap already relieves it)
    panel inner face   y = 36.0  for z 10.4 .. 65     <- flush with the box, zero clearance
    box rear face      y = 36.0  flat, no flutes

Both planes are tangent to the same cylinder of radius HingeAxisFromRear about the hinge
axis, so rotating the lid does not open a gap between them at anything like a useful rate.
Measured, box vs. rear panel:

    deg     gap_mm
    0.0     0.0000
    0.5     0.0002
    1.0     0.0008
    2.0     0.0033
    4.0     0.0132          <- still 13 microns at four degrees open

The gap grows as theta^2, so the panel stays within 0.1 mm of the box for the last ELEVEN
degrees of travel and within 0.3 mm for the last NINETEEN. Printed surface roughness alone
is +/-0.05..0.1 mm, so the whole final approach is a rub. The lid can be forced shut; it
cannot close under its own weight. The top plate is innocent — it is at 0.2349 mm at the
same 4 degrees, eighteen times further away.

This is the SAME defect class as the zero running clearance macro 20 fixed, on the SAME
face, found the same way: by measuring distToShape rather than common().Volume. See "THE
TWO CHECKS THAT PASS WHILE THE MODEL IS WRONG" in CLAUDE.md.

WHY A SECOND POCKET AND NOT A TALLER PocketHingeWrap
-----------------------------------------------------
The obvious fix is to raise SketchHingeWrap's top edge from PanelBottomZ to Height. It does
not work, because that pocket is deliberately NARROW:

    PocketHingeWrap  Length = Width - 2*HingeTabThickness = 97   ->  x +/-48.5 only
    rear panel                                   107 wide        ->  x +/-53.5

The 5 mm strip at each end is excluded so the cut cannot eat the knuckles, which live at
|x| > 48.5 between z 0 and 10. Two of the measured jamming contacts are at x = +/-53.5,
exactly inside those excluded strips. A taller PocketHingeWrap would leave them grazing.

Above PanelBottomZ there are no knuckles (the disc tops out at z = HingeAxisFromBottom +
HingeTabRadius = 10.0, and PanelBottomZ = 10.4), so the upper relief can safely run the FULL
width. Hence a second pocket, ThroughAll and symmetric, spanning z from PanelBottomZ to
above the panel top.

It reuses HingeSwingClearance — the same knob PocketHingeWrap already cuts with, for the
same physical interface (lid rear panel inner face vs. box rear). No new clearance Param:
rule 5 is about not conflating DIFFERENT concerns, and this is the same one.

WHAT THIS DELIBERATELY DOES NOT DO
-----------------------------------
It does not move the panel outboard in Y, and it does not touch FooterHeight. Cutting the
INNER face only leaves the outer face at Depth/2 + WallThickness, so the print-pose bed
plane is untouched and the footer flare does not grow. Moving the panel instead was tried
during macro 20 and is recorded there as a dead end: in the 90 deg pose closed-frame Y maps
onto print Z, so a 0.5 mm outboard shift drops the panel to ZMin -2.5 while the box stays at
-2.0, and the slicer rests the part on the lid.

Cost: the panel goes from WallThickness to WallThickness - HingeSwingClearance (2.0 -> 1.5)
over the relieved area. Measured flat on both sides there — the panel carries no flutes, its
outer face is a constant y = 38.0 — so 1.5 mm is solid wall, about three and a half
extrusions at a 0.42 width. It is not the structural path either; the hinge load goes
through the bottom step, which keeps its full section.

AND A THIRD COINCIDENT SURFACE, FOUND WHEN THE FIRST FIX STILL MEASURED ZERO
----------------------------------------------------------------------------
Relieving y = 36 alone left the closed gap at 0.0000, because the panel's inner face was
only one of the contacts. Measured at x = 50, y = 31 (the hinge axis), scanning z:

    lid  material   z 0..1.6,  8.4..10,  10..10.4
    box  material   z 2..8,    10.4..20

The lid fills to exactly 10.4 and the box starts at exactly 10.4, because

    PanelBottomZ    = HingeAxisFromBottom + HingeTabRadius + HingeTabClearance
    socket bore top = HingeAxisFromBottom + HingeTabRadius + HingeTabClearance

are the SAME expression. The knuckle disc tops out at 10.0 and has its 0.4 mm; the panel's
step above it filled that clearance solid. PanelBottomZ now carries + HingeSwingClearance,
which is what HingeWrapRadius already does for the concentric case.

The residual closed gap after all three fixes is the knuckle journal fit itself,
HingeTabClearance = 0.4 mm. That one is CONCENTRIC with the hinge axis, so it is constant
through the whole swing and never resists closing - which is exactly why MIN_CLOSED_GAP is
set below it rather than above.

SideWallThickness 6 -> 8
------------------------
Bradley's second complaint, and it is measurable rather than aesthetic:

    hinge web    SideWallThickness - (HingeTabThickness + HingeTabClearance)
                 6 - 5.4 = 0.60 mm   ->   8 - 5.4 = 2.60 mm
    magnet edge  SideWallThickness/2 - (MagnetDia/2 + MagnetFit)
                 3 - 2.05 = 0.95 mm  ->   4 - 2.05 = 1.95 mm

Width is derived (CardLength + 2*CardClearance + 2*SideWallThickness), so this grows the
box OUTWARD 107 -> 111 and leaves the interior at 95 x 68 x 63 exactly as it is. The cards
are unaffected; what it costs is plate width, and 111 is inside the 120 mm budget macro 22
set from CAD_STANDARDS.

Idempotent. Restores SideWallThickness and removes the new features if anything fails.

Run: Macro -> Macros... -> 27-panel_relief_and_walls -> Execute
"""

import re
import FreeCAD
import Part
import Sketcher

# ------------------------------------------------------------------ the dials
NEW_SIDE_WALL = 8.0
MAX_WIDTH = 120.0          # CAD_STANDARDS plate budget, as used by macro 22
MIN_CLOSED_GAP = 0.35      # a real clearance. The floor is the knuckle journal fit,
                           # HingeTabClearance 0.4, which is CONCENTRIC and so constant
                           # through the swing - it never resists closing.
MIN_WEB = 2.0
# ------------------------------------------------------------------

P = "<<Params>>#VarSet."
DOCS = ("Params", "MagicCardBox", "Lid", "MagicCardAssembly")
V = FreeCAD.Vector

vs = FreeCAD.getDocument("Params").getObject("VarSet")
boxdoc = FreeCAD.getDocument("MagicCardBox")
liddoc = FreeCAD.getDocument("Lid")
rearbody = liddoc.getObject("Body001")
log = []

before = {n: float(getattr(vs, n)) for n in ("SideWallThickness", "Width")}
before["interior"] = before["Width"] - 2 * before["SideWallThickness"]
before["web"] = before["SideWallThickness"] - (vs.HingeTabThickness.Value
                                               + vs.HingeTabClearance.Value)
tip_before = rearbody.Tip
prev_pbz_expr = dict(vs.ExpressionEngine).get("PanelBottomZ")
before["PanelBottomZ"] = float(vs.PanelBottomZ)


def check_body_order(bd):
    """Group order must equal the BaseFeature chain. A mismatch is invisible to every
    geometric test and only bites later, when FreeCAD re-derives one from the other."""
    grp = [x.Name for x in bd.Group if "BaseFeature" in x.PropertiesList]
    roots = [x for x in bd.Group
             if "BaseFeature" in x.PropertiesList and x.BaseFeature is None]
    chain, seen, node = [], set(), (roots[0] if roots else None)
    while node is not None and node.Name not in seen:
        seen.add(node.Name)
        chain.append(node.Name)
        nxt = [x for x in bd.Group if "BaseFeature" in x.PropertiesList
               and x.BaseFeature is not None and x.BaseFeature.Name == node.Name]
        node = nxt[0] if nxt else None
    stranded = [x.Name for x in bd.Group
                if "BaseFeature" in x.PropertiesList and x.Name not in seen]
    if stranded:
        raise RuntimeError("%s: features unreachable or in a BaseFeature cycle: %s"
                           % (bd.Name, stranded))
    if grp != chain:
        raise RuntimeError("%s: Group order != BaseFeature chain\n  group %s\n  chain %s"
                           % (bd.Name, grp, chain))
    if chain and bd.Tip.Name != chain[-1]:
        raise RuntimeError("%s: Tip is %s but the chain ends at %s"
                           % (bd.Name, bd.Tip.Name, chain[-1]))


def origin_plane(body, role):
    for f in body.Origin.OriginFeatures:
        if f.Role == role:
            return f
    raise RuntimeError("body %s has no %s" % (body.Name, role))


# ------------------------------------------------------------------ guards, before touching
new_width = (vs.CardLength.Value + 2 * vs.CardClearance.Value + 2 * NEW_SIDE_WALL)
new_web = NEW_SIDE_WALL - (vs.HingeTabThickness.Value + vs.HingeTabClearance.Value)
errs = []
if new_width > MAX_WIDTH:
    errs.append("Width would be %.1f, over the %.1f plate budget" % (new_width, MAX_WIDTH))
if new_web < MIN_WEB:
    errs.append("hinge web would be %.2f, under %.2f" % (new_web, MIN_WEB))
if vs.HingeSwingClearance.Value >= vs.WallThickness.Value - 0.8:
    errs.append("relief %.2f would leave the panel under 0.8 mm of the %.2f wall"
                % (vs.HingeSwingClearance.Value, vs.WallThickness.Value))
if vs.PanelBottomZ.Value < vs.HingeAxisFromBottom.Value + vs.HingeTabRadius.Value:
    errs.append("PanelBottomZ %.2f is below the knuckle top %.2f - a full-width cut there "
                "would eat the knuckles"
                % (vs.PanelBottomZ.Value,
                   vs.HingeAxisFromBottom.Value + vs.HingeTabRadius.Value))
if errs:
    raise RuntimeError("27 refuses to run: " + "; ".join(errs))

created = []


def recompute_all():
    for n in DOCS:
        FreeCAD.getDocument(n).recompute(None, True, True)


def rollback(why):
    rearbody.Tip = tip_before
    for o in reversed(created):
        try:
            liddoc.removeObject(o.Name)
        except Exception:
            pass
    vs.SideWallThickness = before["SideWallThickness"]
    vs.setExpression("PanelBottomZ", prev_pbz_expr)
    tip_before.Visibility = True
    recompute_all()
    raise RuntimeError("%s - SideWallThickness restored to %.2f, new features removed"
                       % (why, before["SideWallThickness"]))


# ------------------------------------------------------------------ 1. the panel relief
skp = liddoc.getObject("SketchPanelRelief")
if skp is None:
    skp = rearbody.newObject("Sketcher::SketchObject", "SketchPanelRelief")
    skp.AttachmentSupport = [(origin_plane(rearbody, "YZ_Plane"), "")]
    skp.MapMode = "FlatFace"
    skp.Label = "PanelRelief"
    created.append(skp)
    log.append("Lid/SketchPanelRelief created on Body001 YZ_Plane")
else:
    for path, _ in list(skp.ExpressionEngine):
        if re.match(r"\.?Constraints\[\d+\]$", path):
            skp.setExpression(path, None)
    skp.deleteAllConstraints()
    skp.deleteAllGeometry()
    log.append("Lid/SketchPanelRelief rebuilt")

# Sketch X is global Y, sketch Y is global Z (same convention as SketchHingeWrap).
y_in = vs.Depth.Value / 2 - vs.HingeAxisFromRear.Value - vs.HingeTabRadius.Value
y_out = vs.Depth.Value / 2 + vs.HingeSwingClearance.Value
z_lo = vs.PanelBottomZ.Value
z_hi = vs.Height.Value + vs.LidTopThickness.Value      # overshoot the panel top cleanly
pts = [V(y_in, z_lo, 0), V(y_out, z_lo, 0), V(y_out, z_hi, 0), V(y_in, z_hi, 0)]
for i in range(4):
    skp.addGeometry(Part.LineSegment(pts[i], pts[(i + 1) % 4]), False)
for i in range(4):
    skp.addConstraint(Sketcher.Constraint("Coincident", i, 2, (i + 1) % 4, 1))
skp.addConstraint(Sketcher.Constraint("Horizontal", 0))
skp.addConstraint(Sketcher.Constraint("Horizontal", 2))
skp.addConstraint(Sketcher.Constraint("Vertical", 1))
skp.addConstraint(Sketcher.Constraint("Vertical", 3))
i_x0 = skp.addConstraint(Sketcher.Constraint("DistanceX", -1, 1, 0, 1, y_in))
i_x1 = skp.addConstraint(Sketcher.Constraint("DistanceX", -1, 1, 1, 1, y_out))
i_y0 = skp.addConstraint(Sketcher.Constraint("DistanceY", -1, 1, 0, 1, z_lo))
i_y1 = skp.addConstraint(Sketcher.Constraint("DistanceY", -1, 1, 2, 1, z_hi))
skp.setExpression("Constraints[%d]" % i_x0,
                  P + "Depth / 2 - " + P + "HingeAxisFromRear - " + P + "HingeTabRadius")
skp.setExpression("Constraints[%d]" % i_x1,
                  P + "Depth / 2 + " + P + "HingeSwingClearance")
skp.setExpression("Constraints[%d]" % i_y0, P + "PanelBottomZ")
skp.setExpression("Constraints[%d]" % i_y1, P + "Height + " + P + "LidTopThickness")
log.append("relief window  y %.2f..%.2f   z %.2f..%.2f  (all bound)"
           % (y_in, y_out, z_lo, z_hi))

pkp = liddoc.getObject("PocketPanelRelief")
if pkp is None:
    pkp = rearbody.newObject("PartDesign::Pocket", "PocketPanelRelief")
    pkp.Profile = skp
    pkp.Label = "PanelRelief"
    created.append(pkp)
    log.append("Lid/PocketPanelRelief created")
pkp.Midplane = False          # clear the legacy flag FIRST - see CLAUDE.md
pkp.SideType = "Symmetric"
pkp.Type = "ThroughAll"       # full panel width; no knuckles live above PanelBottomZ
if pkp.BaseFeature is None:
    pkp.BaseFeature = tip_before
skp.Visibility = False
for o in rearbody.Group:
    if getattr(o, "Visibility", False) and o.Name != pkp.Name:
        o.Visibility = False           # Tip moves; visibility does not follow it (macro 24)
pkp.Visibility = True
rearbody.Tip = pkp
log.append("Body001 Tip %s -> %s (ThroughAll, symmetric, full width)"
           % (tip_before.Name, pkp.Name))

# ------------------------------------------------------------------ 2. thicker side walls
vs.SideWallThickness = NEW_SIDE_WALL
log.append("SideWallThickness %.2f -> %.2f  (Width %.2f -> %.2f, derived)"
           % (before["SideWallThickness"], NEW_SIDE_WALL, before["Width"], new_width))

# ------------------------------------------------------------------ 3. clearance under the step
# PanelBottomZ carried the socket bore's top EXACTLY:
#     PanelBottomZ    = HingeAxisFromBottom + HingeTabRadius + HingeTabClearance
#     socket bore top = HingeAxisFromBottom + HingeTabRadius + HingeTabClearance
# Identical expressions, so the lid's step packed the last 0.4 mm of the socket's radial
# clearance solid against the box and the two met face to face at z = 10.4 - measured at
# x = 50, y = 31: lid material 8.4..10.4, box material 10.4..20. The knuckle DISC has its
# proper clearance (it tops out at 10.0); the step above it had none.
#
# Compare HingeWrapRadius = HingeTabRadius + HingeSwingClearance, which carries the term.
# This one was simply missing it. Same defect family as the r=5.000 ride macro 20 fixed.
# PanelBottomZ carried the socket BORE's top:
#     PanelBottomZ = HingeAxisFromBottom + HingeTabRadius + HingeTabClearance  = 10.4
# so the lid's step top face had its inner corner at radius 5.4 from the hinge axis - sitting
# exactly ON the bore. That is a theta^2 approach contact, identical in form to the panel-face
# graze and, measured, the DOMINANT one: back-solving gap = r*(1-cos theta) from the approach
# table gives r = 5.42, the bore, not the panel face's 5.0. Relieving the panel alone left the
# closing approach bit-identical, which is how this was found.
#
# Raising it is wrong - tried and measured. +HingeSwingClearance puts the corner at radius 5.9,
# OUTSIDE the bore and into solid side wall; that run failed with a single contact at
# (50.5, 31.0, 10.9). The lid fills the socket from BELOW, so clearance means coming DOWN.
#
# Down to the knuckle radius. The lid's material inside the socket then never exceeds
# HingeTabRadius, so its clearance to the bore is HingeTabClearance - the same 0.4 mm journal
# fit the disc already has, instead of zero. This also restores what CLAUDE.md said the bound
# was for in the first place ("at or above HingeAxisFromBottom + HingeAxisFromRear" = 10.0);
# the + HingeTabClearance term was the accident.
vs.setExpression("PanelBottomZ", "HingeAxisFromBottom + HingeTabRadius")
# Read the TARGET, not vs.PanelBottomZ - the expression has not propagated until the
# recompute below, so reading it here logs the stale value.
_pbz_new = vs.HingeAxisFromBottom.Value + vs.HingeTabRadius.Value
log.append("PanelBottomZ %.2f -> %.2f  (bore top -> knuckle top; corner radius %.2f -> %.2f "
           "against a %.2f bore)"
           % (before["PanelBottomZ"], _pbz_new,
              before["PanelBottomZ"] - vs.HingeAxisFromBottom.Value,
              _pbz_new - vs.HingeAxisFromBottom.Value,
              vs.HingeTabRadius.Value + vs.HingeTabClearance.Value))

recompute_all()

# ------------------------------------------------------------------ verify
bad = ["%s/%s" % (n, o.Name) for n in ("MagicCardBox", "Lid")
       for o in FreeCAD.getDocument(n).Objects
       if any(s in (list(getattr(o, "State", []) or [])) for s in ("Invalid", "Error"))]
if bad:
    rollback("invalid features: " + ", ".join(bad))

for _bd in (rearbody, liddoc.getObject("Body"), boxdoc.getObject("Body")):
    check_body_order(_bd)
log.append("Group order == BaseFeature chain on all three bodies")

box = boxdoc.getObject("Body").Tip.Shape
rear = liddoc.getObject(rearbody.Tip.Name).Shape
top = liddoc.getObject(liddoc.getObject("Body").Tip.Name).Shape
for nm, s in (("box", box), ("lid rear", rear), ("lid top", top)):
    if not (s.isValid() and s.isClosed() and len(s.Solids) == 1):
        rollback("%s is not a single closed valid solid" % nm)
if rear.distToShape(top)[0] > 1e-6:
    rollback("lid bodies no longer touch - would export as two meshes")

interior = vs.Width.Value - 2 * vs.SideWallThickness.Value
if abs(interior - before["interior"]) > 1e-6:
    rollback("interior changed %.2f -> %.2f; the cards must not be affected"
             % (before["interior"], interior))

ay = vs.Depth.Value / 2 - vs.HingeAxisFromRear.Value
az = vs.HingeAxisFromBottom.Value
ctr = V(0, ay, az)
ax = V(1, 0, 0)

# THE number this macro exists for: the gap at and just off closed.
approach = []
for deg in (0.0, 1.0, 2.0, 4.0):
    a = rear.copy()
    a.rotate(ctr, ax, -deg)
    approach.append((deg, box.distToShape(a)[0]))
# The whole-shape minimum distance is NOT the right gate for this macro, and treating it as
# one cost several rounds. It is dominated by the hinge, where surfaces are SUPPOSED to be
# close: the knuckle journal fit is HingeTabClearance 0.4, and the step's top face sits on
# the socket bore at 0.0 (defect B, pre-existing - this macro neither causes nor fixes it).
# What this macro must prove is that the PANEL face which jammed is now clear, so that is
# measured directly, face to face, below. The whole-shape number is reported, with its
# contact points, as information.
closed_contacts = sorted({(round(q.x, 2), round(q.y, 2), round(q.z, 2))
                          for _p, q, *_r in box.distToShape(rear)[1]})

# THE GATE: the panel's inner face against the box's rear face, measured directly.
BOX_REAR_Y = vs.Depth.Value / 2


def panel_inner_y(x, z):
    cs = rear.common(Part.makeLine(V(x, BOX_REAR_Y - 6.0, z), V(x, BOX_REAR_Y + 6.0, z)))
    ys = [v.Point.y for e in cs.Edges for v in e.Vertexes]
    return min(ys) if ys else None


face_probe = []
for _x in (0.0, vs.Width.Value / 2 - 30.0, vs.Width.Value / 2 - 1.0):
    for _z in (20.0, 40.0, 60.0):
        _y = panel_inner_y(_x, _z)
        face_probe.append((_x, _z, _y, None if _y is None else round(_y - BOX_REAR_Y, 4)))
_missing = [(x, z) for x, z, y, _c in face_probe if y is None]
if _missing:
    rollback("no panel material found at %s - the probe is in the wrong place" % _missing)
worst_face = min(c for _x, _z, _y, c in face_probe)
if worst_face < MIN_CLOSED_GAP:
    rollback("panel-to-box face clearance is %.4f mm, under the %.2f mm target; probe %s"
             % (worst_face, MIN_CLOSED_GAP, face_probe))

sweep = []
for deg in (0, 15, 30, 45, 60, 75, 90):
    a = rear.copy()
    a.rotate(ctr, ax, -deg)
    b = top.copy()
    b.rotate(ctr, ax, -deg)
    sweep.append((deg, box.common(a).Volume + box.common(b).Volume,
                  min(box.distToShape(a)[0], box.distToShape(b)[0])))
worst = max(v for _, v, _ in sweep)
if worst > 0.5:
    rollback("swing interferes by %.3f mm3" % worst)
if min(d for dg, _, d in sweep if dg >= 30) < 0.35:
    rollback("running clearance dropped below 0.35 mm")

r90 = rear.copy()
r90.rotate(ctr, ax, -90)
t90 = top.copy()
t90.rotate(ctr, ax, -90)
lowest = min(box.BoundBox.ZMin, r90.BoundBox.ZMin, t90.BoundBox.ZMin)
float_by = box.BoundBox.ZMin - lowest
if float_by > 1e-6:
    rollback("box would float %.3f mm above the bed in the print pose" % float_by)


def span_x(shape, y, z, x1):
    """Material intervals along +X at (y, z). Measures the solid, not the Params."""
    cs = shape.common(Part.makeLine(V(0.0, y, z), V(x1, y, z)))
    segs = []
    for e in cs.Edges:
        xs = [v.Point.x for v in e.Vertexes]
        segs.append((round(min(xs), 3), round(max(xs), 3)))
    return sorted(segs)


def panel_thickness(z):
    cs = rear.common(Part.makeLine(V(0.0, 20.0, z), V(0.0, 45.0, z)))
    ys = [v.Point.y for e in cs.Edges for v in e.Vertexes]
    return (round(min(ys), 3), round(max(ys), 3)) if ys else None


half = vs.Width.Value / 2
web_span = span_x(box, ay, az, half + 1)
mag_span = span_x(box, -vs.Depth.Value / 2 + vs.MagnetFromFront.Value,
                  vs.Height.Value - vs.MagnetThickness.Value / 2, half + 1)

print("=== 27-panel_relief_and_walls ===")
for line in log:
    print("  " + line)
print("  SideWallThickness %.2f -> %.2f   Width %.2f -> %.2f   interior %.2f (unchanged)"
      % (before["SideWallThickness"], vs.SideWallThickness.Value,
         before["Width"], vs.Width.Value, interior))
print("  hinge web  %.2f -> %.2f mm" % (before["web"], new_web))
print("  PanelBottomZ %.2f -> %.2f  (was the socket bore top; now the knuckle top)"
      % (before["PanelBottomZ"], vs.PanelBottomZ.Value))
print("  PANEL FACE vs BOX REAR - the gate. (x, z, panel_inner_y, clearance)")
for _row in face_probe:
    print("     %s" % (_row,))
print("  worst panel face clearance %.4f mm  (box rear face at y=%.2f)"
      % (worst_face, BOX_REAR_Y))
print("  whole-shape closed contacts (hinge, expected): %d at %s"
      % (len(closed_contacts), closed_contacts[:8]))
print("  CLOSING APPROACH (box vs rear panel) - this is what the print failed on")
print("      deg      gap_mm      was")
for (deg, g), was in zip(approach, (0.0000, 0.0008, 0.0033, 0.0132)):
    print("     %4.1f    %8.4f    %8.4f" % (deg, g, was))
print("  swing  deg   interf_mm3   min_gap_mm")
for deg, v, d in sweep:
    print("        %4d   %9.4f   %9.4f" % (deg, v, d))
print("  print pose ZMin  box %.3f  panel %.3f  top %.3f   box floats %.3f"
      % (box.BoundBox.ZMin, r90.BoundBox.ZMin, t90.BoundBox.ZMin, float_by))
print("  panel section y (inner, outer)  z=20 %s   z=40 %s   z=60 %s"
      % (panel_thickness(20.0), panel_thickness(40.0), panel_thickness(60.0)))
print("  side wall along +X at hinge axis   %s" % web_span)
print("  side wall along +X at the magnet   %s" % mag_span)
print("  SketchPanelRelief: DoF=%d fully=%s" % (skp.solve(), skp.FullyConstrained))
print("  box vol %.2f   lid rear vol %.2f   lid top vol %.2f"
      % (box.Volume, rear.Volume, top.Volume))
touched = ["%s/%s" % (n, o.Name) for n in DOCS
           for o in FreeCAD.getDocument(n).Objects
           if "Touched" in (list(getattr(o, "State", []) or []))]
print("  still Touched: %d %s" % (len(touched), touched if touched else ""))
print("  re-solve the assembly Revolute joint after this (macro 05).")
print("NOT SAVED.")
