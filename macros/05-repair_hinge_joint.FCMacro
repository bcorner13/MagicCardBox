# -*- coding: utf-8 -*-
"""
05-repair_hinge_joint.FCMacro — MagicCardBox

Repairs `MagicCardAssembly/Joint` (Revolute) after the box or lid feature tree changes.

WHY THIS KEEPS HAPPENING (defect D4)
------------------------------------
The joint stores its references as NAMED FACES — `Box001: Body.Face21`,
`Lid: Body001.Face13`. Any feature added to either body renumbers faces, the reference
stops resolving (FreeCAD rewrites it as `Body.?Face21`, the `?` marking it dead), and the
joint goes Invalid. Adding the footer relief pocket did exactly that.

...BUT THAT IS ONLY THE LOUD HALF OF D4. Renumbering can also land the stored name on a
DIFFERENT, PERFECTLY VALID FACE. Then there is no `?`, nothing goes Invalid, the joint
reads Up-to-date, and the breakage only appears on the next recompute, when FreeCAD
re-derives the joint frame from the wrong face and flings the assembly across the screen.
Macro 55 (2026-09-23) triggered exactly that. See `needs_repair()` below — this macro was
upgraded then, because as originally written it would have printed "nothing was dead".

Rather than hard-coding a replacement face number — which would just break again on the
next feature — this macro finds the correct faces BY GEOMETRY:

  box side : the flat circular END DISC of radius HingePinDia/2 centred on the hinge
             axis, +X side  (the end of the printed hinge pin, at x = 46.5 nominal)
  lid side : the flat circular END DISC of radius HingePinDia/2 + HingePinClearance
             centred on the hinge axis, +X side  (bottom of the blind hole in the tab)

It matches on the DISC, not the cylindrical wall. The joint frame sits at the centre of
the disc (x = 46.5); the cylinder's centre of mass is its midpoint (x = 45), so matching
the cylinder shifts the whole assembly by 1.5 mm. Discs are identified by area = pi*r^2,
which also distinguishes the pin end from any other planar face on the axis.

Both are located by matching centre and radius against the Params values, so the macro
stays correct when Depth, the hinge params, or the feature tree change. Re-run it any
time the joint goes Invalid.

TWO THINGS THIS MACRO MUST NOT DO (learned the hard way, 2026-09-13)
--------------------------------------------------------------------
1. Do NOT re-point a reference that still resolves. Assigning Reference1/Reference2 makes
   FreeCAD re-derive Placement1/Placement2 from the newly picked face. Re-pointing the
   still-valid lid reference moved the joint frame from the cylinder's end (x=46.5) to its
   midpoint (x=45) and flipped Placement2's rotation from (0,-90,180) to (90,0,90). The
   joint then solved happily into a COMPLETELY DIFFERENT pose -- the lid swung 90 deg out,
   bbox Y 47..116 instead of sitting closed on the box. An Up-to-date joint is not proof
   of a correct joint.
2. Therefore: capture Placement1/Placement2 first, repair only the dead reference (the one
   FreeCAD has rewritten with a '?'), then write the captured placements back.

The macro asserts afterwards that the Lid link's placement is unchanged, and refuses to
report success if it moved.

Run: Macro -> Macros... -> 05-repair_hinge_joint -> Execute
"""

import FreeCAD

TOL = 1e-6

asm = FreeCAD.getDocument("MagicCardAssembly")
mb = FreeCAD.getDocument("MagicCardBox")
ld = FreeCAD.getDocument("Lid")
vs = FreeCAD.getDocument("Params").getObject("VarSet")

aY = vs.Depth.Value / 2 - vs.HingeAxisFromRear.Value
aZ = vs.HingeAxisFromBottom.Value
r_pin = vs.HingePinDia.Value / 2.0
r_hole = r_pin + vs.HingePinClearance.Value


def find_disc(shape, radius, label):
    """The flat circular END face on the hinge axis, +X side, of the given radius.

    NOT the cylindrical wall. The joint's frame sits at the centre of the pin's end
    disc (x = 46.5 at nominal); picking the cylinder instead puts the frame at the
    cylinder's midpoint (x = 45) and shifts the whole assembly by 1.5 mm.
    """
    import math
    want_area = math.pi * radius * radius
    hits = []
    for i, f in enumerate(shape.Faces):
        if f.Surface.TypeId != "Part::GeomPlane":
            continue
        c = f.CenterOfMass
        if abs(c.y - aY) > 1e-3 or abs(c.z - aZ) > 1e-3 or c.x <= 0:
            continue
        if abs(f.Area - want_area) > 1e-2:
            continue
        hits.append(("Face%d" % (i + 1), round(c.x, 3), round(f.Area, 3)))
    if not hits:
        raise RuntimeError("%s: no flat disc r=%.3f centred on the hinge axis "
                           "(Y=%.3f Z=%.3f)" % (label, radius, aY, aZ))
    hits.sort(key=lambda h: -h[1])                # outermost first
    return hits


box_body = mb.getObject("Body")
lid_back = ld.getObject("Body001")
box_hits = find_disc(box_body.Shape, r_pin, "box pin end face")
lid_hits = find_disc(lid_back.Shape, r_hole, "lid hole end face")

box_face = box_hits[0][0]
lid_face = lid_hits[0][0]

j = asm.getObject("Joint")
link_lid = asm.getObject("Lid")
link_box = asm.getObject("Box001")

# Capture BEFORE touching anything — these are what must survive.
P1 = FreeCAD.Placement(j.Placement1)
P2 = FreeCAD.Placement(j.Placement2)
lid_pose_before = FreeCAD.Placement(link_lid.Placement)
ref1_before, ref2_before = str(j.Reference1), str(j.Reference2)
state_before = list(j.State)


def is_dead(ref):
    """FreeCAD rewrites an unresolvable subelement with a '?' prefix."""
    return any("?" in s for s in ref[1])


def needs_repair(ref, want_sub):
    """Repair when the reference is DEAD *or* silently points somewhere else.

    UPGRADED 2026-09-23 -- and this macro would NOT have caught the failure that
    prompted it.

    Adding PanelNeckGusset at the tip of Body001 (macro 55) took its face count
    21 -> 23, and the stored `Body001.Face20` SILENTLY re-resolved:

        before   Plane,    area 36.3168 = pi*3.4^2, centre (53.5, 31.5, 5)
                 -> the blind pin-hole's end disc, the correct face
        after    Cylinder, R=0.600, centre (-50.5, 35.7895, 1.4)
                 -> KnuckleArcFillet, on the OPPOSITE side of the box

    No '?'. Nothing Invalid. Joint State ['Up-to-date']. Placement1 still read
    (53.5, 31.5, 5) because FreeCAD had not re-derived it yet -- so every check
    said fine. The moment the assembly was recomputed, Placement1 was re-derived
    from the wrong face and the lid link jumped to X 73..184.

    is_dead() alone therefore reported "nothing was dead" on a joint that was
    bound to the wrong geometry. A reference that re-resolves onto the WRONG
    face is worse than one that dies, because nothing complains (seventh round,
    PanelBottomChamfer -- same lesson, now for assembly joints).

    So: compare the stored name against the face located BY GEOMETRY, and repair
    on mismatch as well as on death.
    """
    if is_dead(ref):
        return True
    return list(ref[1]) != [want_sub, want_sub]


repaired = []
want2 = "Body." + box_face
want1 = "Body001." + lid_face
if needs_repair(j.Reference2, want2):
    why = "dead" if is_dead(j.Reference2) else "pointed at %s, geometry says %s" % (
        list(j.Reference2[1]), want2)
    j.Reference2 = (link_box, [want2, want2])
    repaired.append("Reference2 -> %s (%s)" % (want2, why))
if needs_repair(j.Reference1, want1):
    why = "dead" if is_dead(j.Reference1) else "pointed at %s, geometry says %s" % (
        list(j.Reference1[1]), want1)
    j.Reference1 = (link_lid, [want1, want1])
    repaired.append("Reference1 -> %s (%s)" % (want1, why))

# Writing a reference makes FreeCAD re-derive the joint frames. Put them back.
#
# Placement2 must also be forced to match Placement1. Once HingePinClearance is non-zero the
# pin's end disc (X = 46.1) and the hole's blind end (X = 46.5) are deliberately 0.4 mm apart
# — that gap IS the axial clearance. FreeCAD derives Placement2 from the pin face, so the
# joint then drags the lid 0.4 mm to make the two faces touch, closing the clearance it is
# supposed to have. The assembled pose we want is the tab flush with the side wall's outer
# face, i.e. the lid link unmoved, so both frames sit at the same axial station on the axis.
# ...but only the ROTATION may be restored blindly. The captured POSITION is valid only
# while the hinge has not physically moved, and a Width or SideWallThickness change slides
# it along X: macro 27 took Width 107 -> 111, which moved the pin's end disc 51.1 -> 53.1
# and the hole's blind end 51.5 -> 53.5. Restoring the captured position would have anchored
# the joint 2 mm inboard of the actual hinge and the solver would drag the lid to suit -
# caught by the pose check below, but not fixed by it.
#
# So: position follows the face we just located by geometry; rotation is preserved, because
# that is the part FreeCAD re-derives wrongly (note 1 in the header).
anchor = FreeCAD.Vector(lid_hits[0][1], aY, aZ)
P_new = FreeCAD.Placement(anchor, P1.Rotation)
if (P_new.Base - P1.Base).Length > 1e-9:
    print("  hinge moved: joint anchor %s -> %s (rotation preserved)"
          % (P1.Base, P_new.Base))
j.Placement1 = P_new
j.Placement2 = FreeCAD.Placement(P_new)

for n in ("Params", "MagicCardBox", "Lid", "MagicCardAssembly"):
    FreeCAD.getDocument(n).recompute(None, True, True)

moved = (link_lid.Placement.Base - lid_pose_before.Base).Length
rot_same = link_lid.Placement.Rotation.isSame(lid_pose_before.Rotation, 1e-9)
# FreeCAD re-derives Placement2 from the referenced face on every recompute — assigning it
# does not stick. With HingePinClearance non-zero the pin end (X=46.1) and hole bottom
# (X=46.5) are deliberately that far apart, so the joint settles the lid 0.4 mm inboard.
# That is one end of the joint's axial freedom, not a fault: the printed parts really can
# slide by the clearance. Anything LARGER than the clearance is a genuine mis-solve.
allowed = vs.HingePinClearance.Value + 1e-6
pose_ok = moved <= allowed and rot_same

print("=== 05-repair_hinge_joint ===")
print("  hinge axis  : Y=%.3f  Z=%.3f" % (aY, aZ))
print("  pin end disc : %.3f -> box candidates %s" % (r_pin, box_hits))
print("  hole end disc: %.3f -> lid candidates %s" % (r_hole, lid_hits))
print("  before: Ref1=%s" % ref1_before)
print("          Ref2=%s  State=%s" % (ref2_before, state_before))
print("  repaired: %s" % (", ".join(repaired) if repaired
                          else "nothing needed repair "
                               "(both references resolve AND match the geometry)"))
print("  after : Ref1=%s" % str(j.Reference1))
print("          Ref2=%s" % str(j.Reference2))
print("  Placement1 set: %s" % j.Placement1)
print("  Placement2 set: %s" % j.Placement2)
print("  Lid link pose moved by %.9f mm (allowed <= HingePinClearance %.3f), rotation unchanged=%s  -> %s"
      % (moved, vs.HingePinClearance.Value, rot_same,
         "OK" if pose_ok else "*** POSE CHANGED BEYOND CLEARANCE - DO NOT SAVE ***"))
print("  Joint State: %s" % list(j.State))
problems = []
for n in ("Params", "MagicCardBox", "Lid", "MagicCardAssembly"):
    for o in FreeCAD.getDocument(n).Objects:
        bad = [s for s in (list(getattr(o, "State", []) or []))
               if s in ("Invalid", "Error", "Touched")]
        if bad:
            problems.append("%s/%s: %s" % (n, o.Name, ",".join(bad)))
print("Recompute problems: %d" % len(problems))
for p in problems:
    print("  " + p)
print("NOT SAVED -- verify, then save.")
