# -*- coding: utf-8 -*-
"""
46-magnet_fit_and_leadin.FCMacro

The magnets will not go into the printed pockets. Opens the bore and adds a
45 deg lead-in at each pocket mouth.

WHY A CHAMFER ALONE WOULD NOT HAVE FIXED IT

    MagnetDia 4.00, MagnetFit 0.05 per side  ->  bore Ø4.100
    measured in the solid, identical at the rim and at the pocket floor

  0.05 mm per side is a CAD fit, not an FDM fit. A printed hole comes out
  UNDERSIZE - the inner perimeter's extrusion is laid slightly inboard of the
  nominal path and small bores suffer most - typically 0.1-0.3 mm on diameter.
  So a nominal Ø4.100 bore prints near Ø3.9-4.0 and a Ø4.00 magnet binds along
  the WHOLE DEPTH, not just at the mouth.

  A lead-in helps the magnet START. It cannot help a bore that is undersize all
  the way down. Both are therefore needed, and the fit is the load-bearing half:

    MagnetFit     0.05 -> 0.15 per side   bore Ø4.100 -> Ø4.300
    MagnetLeadIn  0.3 (new)               45 deg lead-in at each mouth

WHAT THE BORE HAS ROOM FOR - checked, not assumed

    outboard wall   bore 53.55 -> side wall 55.5    1.95 -> 1.85 mm
    inboard wall    cavity 47.5 -> bore 49.45       1.95 -> 1.85 mm
    skin under the outer lid flute                  1.00 mm, UNCHANGED

  The skin is MagnetSkin - FluteDepth wherever the outermost flute crosses the
  bore, so widening the bore extends that region but cannot make it thinner.
  Verified below rather than argued.

WHY A TAPERED POCKET AND NOT PartDesign::Chamfer

  A chamfer would need FOUR named edge references (two bores per document), and
  this project has now been bitten twice by named-edge references - Fillet004
  died outright, PanelBottomChamfer silently re-resolved onto the WRONG edge and
  nothing complained. A tapered pocket references a SKETCH and a Param, so there
  is no edge name to go stale.

    mouth radius = MagnetDia/2 + MagnetFit + MagnetLeadIn
    depth        = MagnetLeadIn
    taper        = 45 deg, narrowing, so at full depth the cone radius is
                   exactly MagnetDia/2 + MagnetFit and it meets the bore

  THE TAPER SIGN IS DETERMINED BY MEASUREMENT, not by trusting a convention:
  the macro cuts, measures the mouth and the floor, and flips the sign if the
  cone came out widening instead of narrowing.

  Both lead-ins are appended at the TIP of their body, so no existing edge
  reference is disturbed (the macro 24 / 37 pattern).

Idempotent: safe to re-run. Re-asserts every driving expression on every run,
outside the create branch - macro 38 shipped a version that set its expression
only on creation and silently did nothing on the second run.
"""

import FreeCAD
import Part
import Sketcher
from FreeCAD import Vector

P = "<<Params>>#VarSet."
TARGET_FIT = 0.15
TARGET_LEADIN = 0.3
TAPER = 45.0

R_EXPR = P + "MagnetDia / 2 + " + P + "MagnetFit + " + P + "MagnetLeadIn"
CX_EXPR = P + "Width / 2 - " + P + "SideWallThickness / 2"
CY_EXPR = "-" + P + "Depth / 2 + " + P + "MagnetFromFront"

SPEC = {
    # doc,            body,     new sketch,            new pocket,             plane,         z offset expr,                     reversed
    "MagicCardBox": ("Body",   "SketchMagnetLeadBox", "PocketMagnetLeadBox",  "XY_Plane",    P + "Height",                       False),
    "Lid":          ("Body",   "SketchMagnetLeadLid", "PocketMagnetLeadLid",  "XY_Plane001", P + "Height + " + P + "LidSeatClearance", True),
}


def check_body_order(body, problems):
    feats = [o for o in body.Group if hasattr(o, "BaseFeature")]
    roots = [o for o in feats if o.BaseFeature is None]
    if len(roots) != 1:
        problems.append("expected 1 chain root, found %d" % len(roots)); return
    chain, seen, cur = [], set(), roots[0]
    while cur is not None:
        if cur.Name in seen:
            problems.append("CYCLE at %s" % cur.Name); return
        seen.add(cur.Name); chain.append(cur)
        nxt = [o for o in feats if o.BaseFeature is cur]
        if len(nxt) > 1:
            problems.append("%s is BaseFeature of %d" % (cur.Name, len(nxt))); return
        cur = nxt[0] if nxt else None
    if [o.Name for o in feats] != [o.Name for o in chain]:
        problems.append("%s: Group order != BaseFeature chain" % body.Name)
    if body.Tip is not chain[-1]:
        problems.append("%s: Tip %s != chain end %s" % (body.Name, body.Tip.Name, chain[-1].Name))


def build(doc_name, log):
    body_n, sk_n, pk_n, plane_n, zexpr, reversed_ = SPEC[doc_name]
    doc = FreeCAD.getDocument(doc_name)
    body = doc.getObject(body_n)
    vs = FreeCAD.getDocument("Params").getObject("VarSet")

    sk = doc.getObject(sk_n)
    if sk is None:
        sk = body.newObject("Sketcher::SketchObject", sk_n)
        sk.AttachmentSupport = [(doc.getObject(plane_n), [""])]
        sk.MapMode = "FlatFace"
        cx = float(vs.Width.Value) / 2 - float(vs.SideWallThickness.Value) / 2
        cy = -float(vs.Depth.Value) / 2 + float(vs.MagnetFromFront.Value)
        r = float(vs.MagnetDia.Value) / 2 + TARGET_FIT + TARGET_LEADIN
        sk.addGeometry(Part.Circle(Vector(cx, cy, 0), Vector(0, 0, 1), r), False)
        sk.addGeometry(Part.Circle(Vector(-cx, cy, 0), Vector(0, 0, 1), r), False)
        sk.addConstraint(Sketcher.Constraint("DistanceX", 0, 3, cx))
        sk.addConstraint(Sketcher.Constraint("DistanceY", 0, 3, cy))
        sk.addConstraint(Sketcher.Constraint("Radius", 0, r))
        sk.addConstraint(Sketcher.Constraint("DistanceX", 1, 3, -cx))
        sk.addConstraint(Sketcher.Constraint("DistanceY", 1, 3, cy))
        sk.addConstraint(Sketcher.Constraint("Radius", 1, r))
        log.append("%s: created %s" % (doc_name, sk_n))
    # re-assert EVERY run, never only on creation
    sk.setExpression(".AttachmentOffset.Base.z", zexpr)
    sk.setExpression("Constraints[0]", CX_EXPR)
    sk.setExpression("Constraints[1]", CY_EXPR)
    sk.setExpression("Constraints[2]", R_EXPR)
    sk.setExpression("Constraints[3]", "-(" + CX_EXPR + ")")
    sk.setExpression("Constraints[4]", CY_EXPR)
    sk.setExpression("Constraints[5]", R_EXPR)

    pk = doc.getObject(pk_n)
    if pk is None:
        pk = body.newObject("PartDesign::Pocket", pk_n)
        pk.Profile = sk
        pk.Reversed = reversed_
        pk.Midplane = False
        pk.SideType = "One side"
        log.append("%s: created %s at the body tip" % (doc_name, pk_n))
    pk.setExpression("Length", P + "MagnetLeadIn")
    pk.TaperAngle = -TAPER          # sign verified by measurement below
    body.Tip = pk
    doc.recompute()
    return sk, pk


def bore_dia(shape, cx, cy, z):
    """Diameter of the hole at height z, measured across the solid."""
    e = Part.makeLine(Vector(cx - 6, cy, z), Vector(cx + 6, cy, z))
    cc = shape.common(e)
    if not cc.Edges:
        return None
    xs = sorted((s.BoundBox.XMin, s.BoundBox.XMax) for s in cc.Edges)
    if len(xs) < 2:
        return None
    return round(xs[1][0] - xs[0][1], 4)


def main():
    vs = FreeCAD.getDocument("Params").getObject("VarSet")
    mb = FreeCAD.getDocument("MagicCardBox")
    ld = FreeCAD.getDocument("Lid")
    log, problems = [], []

    if "MagnetFit" in dict(vs.ExpressionEngine):
        raise RuntimeError("MagnetFit is expression-driven; it must stay a free input")
    if "MagnetLeadIn" not in vs.PropertiesList:
        vs.addProperty("App::PropertyLength", "MagnetLeadIn", "Magnets",
                       "Depth of the 45 deg lead-in at each magnet pocket mouth. An "
                       "ASSEMBLY aid, not a fit: it helps the magnet start square. The "
                       "bore itself is sized by MagnetFit, which is the half that "
                       "actually decides whether the magnet goes in.")
        log.append("added MagnetLeadIn")
    vs.MagnetLeadIn = TARGET_LEADIN
    before_fit = round(float(vs.MagnetFit), 4)
    vs.MagnetFit = TARGET_FIT
    FreeCAD.getDocument("Params").recompute()
    log.append("MagnetFit %.4f -> %.4f  (bore Ø%.3f -> Ø%.3f)"
               % (before_fit, TARGET_FIT,
                  float(vs.MagnetDia.Value) + 2 * before_fit,
                  float(vs.MagnetDia.Value) + 2 * TARGET_FIT))

    for dn in ("MagicCardBox", "Lid"):
        build(dn, log)
    for dn in ("Params", "Lid", "MagicCardBox", "MagicCardAssembly"):
        FreeCAD.getDocument(dn).recompute()

    # ---------------- verify ----------------
    cx = float(vs.Width.Value) / 2 - float(vs.SideWallThickness.Value) / 2
    cy = -float(vs.Depth.Value) / 2 + float(vs.MagnetFromFront.Value)
    H = float(vs.Height.Value)
    LI = float(vs.MagnetLeadIn.Value)
    want_bore = float(vs.MagnetDia.Value) + 2 * float(vs.MagnetFit)
    want_mouth = want_bore + 2 * LI

    boxS = mb.getObject("Body").Shape
    mouth = bore_dia(boxS, cx, cy, H - 0.02)
    floor = bore_dia(boxS, cx, cy, H - LI - 0.05)

    # THE TAPER SIGN IS NOT TRUSTED - if the cone came out widening, flip and redo
    if mouth is not None and floor is not None and mouth < floor:
        log.append("taper sign was inverted (mouth %.3f < floor %.3f) - flipping" % (mouth, floor))
        for dn in ("MagicCardBox", "Lid"):
            pk = FreeCAD.getDocument(dn).getObject(SPEC[dn][3])
            pk.TaperAngle = TAPER
        for dn in ("Params", "Lid", "MagicCardBox"):
            FreeCAD.getDocument(dn).recompute()
        boxS = mb.getObject("Body").Shape
        mouth = bore_dia(boxS, cx, cy, H - 0.02)
        floor = bore_dia(boxS, cx, cy, H - LI - 0.05)

    log.append("box bore: mouth Ø%s (want ~%.3f), below lead-in Ø%s (want %.3f)"
               % (mouth, want_mouth, floor, want_bore))
    if mouth is None or abs(mouth - want_mouth) > 0.12:
        problems.append("mouth Ø%s != expected %.3f" % (mouth, want_mouth))
    if floor is None or abs(floor - want_bore) > 0.02:
        problems.append("bore below the lead-in is Ø%s, expected %.3f" % (floor, want_bore))

    # walls must survive the wider bore
    walls = {"outboard": round(float(vs.Width.Value) / 2 - (cx + want_bore / 2), 4),
             "inboard": round((cx - want_bore / 2)
                              - (float(vs.Width.Value) / 2 - float(vs.SideWallThickness.Value)), 4)}
    log.append("magnet wall margins %s" % walls)
    for k, v in walls.items():
        if v < 1.0:
            problems.append("%s magnet wall down to %.3f mm" % (k, v))

    for dn in ("MagicCardBox", "Lid"):
        d = FreeCAD.getDocument(dn)
        check_body_order(d.getObject("Body"), problems)
        for o in d.Objects:
            st = o.State or []
            if "Invalid" in st or "Error" in st:
                problems.append("%s/%s %s" % (dn, o.Name, list(st)))

    plate = ld.getObject("Body").Shape
    panel = ld.getObject("Body001").Shape
    for tag, sh in (("box", boxS), ("plate", plate), ("panel", panel)):
        if not (sh.isValid() and sh.isClosed() and len(sh.Solids) == 1):
            problems.append("%s is not a single valid closed solid" % tag)

    import MeshPart
    for tag, sh in (("box", boxS), ("plate", plate)):
        mm = MeshPart.meshFromShape(Shape=sh, LinearDeflection=0.1,
                                    AngularDeflection=0.5, Relative=False)
        if not mm.isSolid():
            problems.append("%s mesh not watertight" % tag)
        if mm.hasNonManifolds():
            problems.append("%s mesh non-manifold" % tag)

    # widening a pocket near the hinge must not have touched the swing
    from FreeCAD import Rotation, Placement
    ay = float(vs.Depth.Value) / 2 - float(vs.HingeAxisFromRear.Value)
    az = float(vs.HingeAxisFromBottom.Value)
    gaps = []
    for deg in (0.0, 45.0, 90.0):
        c = panel.copy()
        c.Placement = Placement(Vector(0, 0, 0), Rotation(Vector(1, 0, 0), -deg),
                                Vector(0, ay, az)).multiply(c.Placement)
        gaps.append((deg, round(boxS.distToShape(c)[0], 4),
                     round(boxS.common(c).Volume, 4)))
    log.append("panel swing %s" % gaps)
    if len(set(g for _, g, _ in gaps)) != 1 or any(v > 1e-4 for _, _, v in gaps):
        problems.append("panel swing changed: %s" % gaps)

    log.append("RESULT: %s" % ("FAIL -> " + "; ".join(problems) if problems else "all checks pass"))
    print("\n".join(log))
    if problems:
        raise RuntimeError("; ".join(problems))


main()
