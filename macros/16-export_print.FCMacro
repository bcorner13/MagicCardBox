# -*- coding: utf-8 -*-
"""
16-export_print.FCMacro — MagicCardBox

Builds the print-ready pose and writes `3mf/MagicCardBox-print.3mf` and
`stl/MagicCardBox-print.stl`.

PRINT POSE
----------
One part, lid rotated 90 deg open about the hinge axis. That angle is not arbitrary: at
exactly 90 deg the lid's rear-panel outer face lands at

    Z = HingeAxisFromBottom - (Depth/2 + LidBackThickness - aY) = -LidBackThickness = -4

with aY = Depth/2 - HingeAxisFromRear, so the HingeAxisFromRear terms cancel exactly. That
is the footer's bottom, -FooterHeight. Box and open lid are therefore COPLANAR and the whole
part sits flat on one plane with no supports.

This now holds BY CONSTRUCTION rather than by coincidence: FooterHeight is DERIVED from
LidBackThickness (macro 34), because they were two free knobs that merely happened to share
a value. Measured bed mismatch 0.0000 mm.

SUPERSEDED 2026-09-14: this read `HingeAxisFromBottom = HingeAxisFromRear + WallThickness -
FooterHeight` = 5 - 7 = -2, from when the rear panel was WallThickness 2 and the footer 2.
The panel is LidBackThickness 4 now and the footer tracks it. Note also that raising the lid
plate by LidSeatClearance (macro 35) does NOT affect this: in the print pose the plate's Z
maps onto Y, not Z, so the bed plane is untouched.

Box and lid are exported as ONE compound object so the slicer keeps their relative positions
and does not try to arrange them as two separate parts. They are NOT fused — the hinge
clearance has to survive into the mesh.

VERIFIED BEFORE WRITING (the macro refuses otherwise)
-----------------------------------------------------
  * minimum distance between box and lid IN THE PRINT POSE >= one nozzle width.
    NOTE this is a DISTANCE check, not an interference check. Every swing test earlier in
    this project used `common().Volume`, which is zero for surfaces that merely TOUCH — it
    passed at every angle while the real gap was 0.025 mm. For a print-in-place part the
    meaningful measure is `distToShape`.
  * both solids valid, closed and single
  * footprint inside the K2 Plus bed

Run: Macro -> Macros... -> 16-export_print -> Execute
"""

import os
import FreeCAD
import Part

NOZZLE = 0.4
BED = 350.0
PROJ = "/Users/bradleycorner/Documents/3dPrinting/Commercial License/MagicCardBox"

mb = FreeCAD.getDocument("MagicCardBox")
ld = FreeCAD.getDocument("Lid")
vs = FreeCAD.getDocument("Params").getObject("VarSet")
V = FreeCAD.Vector

aY = vs.Depth.Value / 2 - vs.HingeAxisFromRear.Value
aZ = vs.HingeAxisFromBottom.Value

box = mb.getObject("Body").Shape.copy()

# FUSE the lid's two bodies. `Body` (top plate) and `Body001` (rear panel + hinge) are
# separate PartDesign solids that TOUCH on a coincident face at Z = Height. Exported as a
# compound they mesh into non-manifold edges — the first export came back
# isSolid()=False, hasNonManifolds()=True, hasSelfIntersections()=True, which slicers may
# refuse or silently mis-fill. They are one printed piece, so fuse them and drop the
# internal coincident faces with removeSplitter().
lid = ld.getObject("Body").Shape.fuse(ld.getObject("Body001").Shape).removeSplitter()
if len(lid.Solids) != 1:
    raise RuntimeError("lid did not fuse into a single solid (%d solids) — the two bodies "
                       "may no longer touch" % len(lid.Solids))
lid.rotate(V(0, aY, aZ), V(1, 0, 0), -90)

# ---- gate 1: real clearance in the print pose -------------------------------
gap = box.distToShape(lid)[0]
if gap < NOZZLE - 1e-6:
    p = box.distToShape(lid)[1][0]
    raise RuntimeError("print-pose gap %.4f mm < one nozzle width %.2f, at "
                       "box(%.2f,%.2f,%.2f) lid(%.2f,%.2f,%.2f) — it would fuse"
                       % (gap, NOZZLE, p[0].x, p[0].y, p[0].z, p[1].x, p[1].y, p[1].z))

# ---- gate 2: solids -----------------------------------------------------------
for tag, s in (("box", box), ("lid", lid)):
    if not s.isValid() or not s.isClosed():
        raise RuntimeError("%s is not a valid closed solid" % tag)

# ---- sit it on Z=0 and centre it on the plate ---------------------------------
comb = Part.makeCompound([box, lid])
b = comb.BoundBox
if b.XLength > BED or b.YLength > BED:
    raise RuntimeError("footprint %.1f x %.1f exceeds the %.0f mm bed"
                       % (b.XLength, b.YLength, BED))
shift = V(-(b.XMin + b.XMax) / 2.0, -(b.YMin + b.YMax) / 2.0, -b.ZMin)
comb.translate(shift)

# ---- write it out --------------------------------------------------------------
name = "MCB_Print"
if name in [d.Name for d in FreeCAD.listDocuments().values()]:
    FreeCAD.closeDocument(name)
doc = FreeCAD.newDocument(name)
obj = doc.addObject("Part::Feature", "MagicCardBox_print")
obj.Shape = comb
doc.recompute()

for sub in ("3mf", "stl"):
    d = os.path.join(PROJ, sub)
    if not os.path.isdir(d):
        os.makedirs(d)

# The files themselves are written by the typed export tools (export_3mf / export_stl)
# against this document, rather than guessing at a Python export API here. This macro's
# job is to build the posed geometry and to REFUSE if it is not printable.

nb = comb.BoundBox
print("=== 16-export_print ===")
print("  print-pose min gap : %.4f mm  (nozzle %.2f)" % (gap, NOZZLE))
print("  lid rotated        : 90 deg; box bottom and open-lid face both at Z=-%.1f before shift"
      % vs.FooterHeight.Value)
print("  footprint          : %.2f x %.2f x %.2f  (bed %.0f)" % (nb.XLength, nb.YLength, nb.ZLength, BED))
print("  sits on Z          : %.3f .. %.3f" % (nb.ZMin, nb.ZMax))
print("  solids in compound : %d" % len(comb.Solids))
print("  export dirs ready: 3mf/ and stl/ — write with export_3mf / export_stl")

# ---- verify whatever is already on disk ------------------------------------------
#
# WHY THIS EXISTS. On 2026-09-13 3mf/MagicCardBox-fluted.3mf sat in the repo for three
# commits as a Creality Print PROJECT file saved back over the export's name. Creality
# references its geometry elsewhere in the container, so 3D/3dmodel.model was a 1,376-byte
# metadata stub with ZERO triangles. It went unnoticed because the STL beside it was
# byte-perfect and every mesh check was run against the STL. Byte-comparing a 3MF is
# useless (zip metadata differs on every write), and a good STL says nothing about the
# file next to it.
#
# Deliberately NOT verified against a freshly tessellated mesh: this macro does not
# perform the export (the typed export_3mf / export_stl tools do), so a locally recomputed
# facet count could differ from theirs on tessellation settings alone and fail honest
# files. What IS checked cannot drift:
#
#   * the 3MF payload contains triangles at all      -> catches a slicer project
#   * 3MF triangle count == STL facet count          -> catches either being stale
#   * STL watertight, manifold, non-self-intersecting, 2 components
#   * bounding box matches the pose built above      -> catches stale geometry
#     (identical for both variants - flutes do not change the bbox)
#
# Run order: this macro -> export_3mf / export_stl -> THIS MACRO AGAIN to confirm.

import re as _re
import zipfile as _zip


def _tris_in_3mf(path):
    """Triangle count from the 3MF payload. Zero means it is not a geometry export."""
    try:
        with _zip.ZipFile(path) as z:
            name = next((n for n in z.namelist() if n.endswith("3dmodel.model")), None)
            if name is None:
                return None, "no 3dmodel.model in container"
            data = z.read(name).decode("utf-8", "replace")
        return len(_re.findall(r"<triangle\b", data)), None
    except Exception as exc:
        return None, str(exc)[:60]


print("  --- export check (files currently on disk) ---")
_expect_bb = (round(nb.XLength, 2), round(nb.YLength, 2), round(nb.ZLength, 2))

# BBOX IS NOT ENOUGH, learned 2026-09-14. Macro 29 filled the front wall's finger slot -
# 2854 mm3 of geometry, and not one millimetre of bounding box. Both stale files sailed
# through this check reporting OK. Volume is the coarse quantity that actually moves when
# the model changes, so it is checked too.
#
# It can only be checked against the variant the model is CURRENTLY in, since the other one's
# geometry is not loaded. The flutes decide which that is.
# SIX published files now: {100, 60} x {smooth, fluted, fluted-label}. This macro can
# only have the model in ONE state at a time, so only that variant gets its volume
# checked and the other five get structural checks. That limitation is precisely why
# macro 41 exists - it exports in-loop and checks every variant fully. A stale
# 100-fluted file missing the whole name plate once measured +0.95% here, inside the
# 1% tolerance, and passed.
# SUPERSEDED FOR BULK WORK BY MACRO 41. That macro drives the whole matrix from
# a table, exports each variant WHILE THE MODEL IS IN THAT STATE, and therefore
# dimension-checks all six instead of only the loaded one. This macro remains
# useful for building/gating a single pose by hand. Keep the two lists in step.
_counts = (100, 60)
_surfaces = ("smooth", "fluted", "fluted-label")


def _surface_now():
    _flutes = not mb.getObject("Pocket009").Suppressed
    _label = not ld.getObject("PocketNamePlate").Suppressed
    if _flutes and _label:
        return "fluted-label"
    return "fluted" if _flutes else "smooth"


_cur_variant = "%d-%s" % (vs.CardCount, _surface_now())
_expect_vol = comb.Volume
_VOL_TOL = 0.01          # 1%: tessellation of the flutes and fillets loses a little volume
_problems = []
for _variant in ["%d-%s" % (_c, _f) for _c in _counts for _f in _surfaces]:
    _3mf = os.path.join(PROJ, "3mf", "MagicCardBox-%s.3mf" % _variant)
    _stl = os.path.join(PROJ, "stl", "MagicCardBox-%s.stl" % _variant)
    if not (os.path.isfile(_3mf) and os.path.isfile(_stl)):
        print("  %-11s not exported yet" % _variant)
        continue
    _t, _err = _tris_in_3mf(_3mf)
    import Mesh as _Mesh
    _m = _Mesh.Mesh(_stl)
    _bb = _m.BoundBox
    _got_bb = (round(_bb.XLength, 2), round(_bb.YLength, 2), round(_bb.ZLength, 2))
    _bad = []
    if _err:
        _bad.append("3mf unreadable: %s" % _err)
    elif _t == 0:
        _bad.append("3MF HAS NO GEOMETRY (%d triangles) - a slicer project, not an export" % _t)
    elif _t != _m.CountFacets:
        _bad.append("3mf %d tris != stl %d facets - one of them is stale" % (_t, _m.CountFacets))
    if not _m.isSolid():
        _bad.append("stl not watertight")
    if _m.hasNonManifolds():
        _bad.append("stl non-manifold")
    if _m.hasSelfIntersections():
        _bad.append("stl self-intersecting")
    if _m.countComponents() != 2:
        _bad.append("stl has %d components, expected 2 (box + fused lid)" % _m.countComponents())
    # DIMENSIONAL checks only against the variant the model is currently in. The others are
    # different boxes on purpose - the 60-card pose is 113.91 x 107.35 against the 100's
    # 113.91 x 132.15 - and comparing them to the loaded geometry reports correct files as
    # stale. Structural checks (triangles, watertight, manifold, components) apply to all four.
    if _variant == _cur_variant:
        if _got_bb != _expect_bb:
            _bad.append("stl bbox %s != posed %s - stale geometry" % (_got_bb, _expect_bb))
        _dv = abs(_m.Volume - _expect_vol) / _expect_vol
        if _dv > _VOL_TOL:
            _bad.append("stl volume %.2f cm3 != posed %.2f cm3 (%.2f%% off) - stale geometry"
                        % (_m.Volume / 1000.0, _expect_vol / 1000.0, _dv * 100.0))
    if _bad:
        _problems.append("%s: %s" % (_variant, "; ".join(_bad)))
        print("  %-11s FAIL  %s" % (_variant, "; ".join(_bad)))
    else:
        _note = ("dims checked, vol %+.2f%%"
                 % ((_m.Volume - _expect_vol) / _expect_vol * 100.0)
                 if _variant == _cur_variant
                 else "structure only (model is %s)" % _cur_variant)
        print("  %-11s OK    %d tris, %.2f cm3, %s, on Z=%.1f  [%s]"
              % (_variant, _m.CountFacets, _m.Volume / 1000.0, _got_bb, _bb.ZMin, _note))
if _problems:
    raise RuntimeError("exports failed verification: " + " | ".join(_problems))

print("NOTE: MCB_Print is a throwaway export document - do not save it into the project.")
